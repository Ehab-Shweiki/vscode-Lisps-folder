(vl-load-com)
;------------------------------------------------------------------------------------------------------------
;------------------------------------------------------------------------------------------------------------
(defun c:PLContinue ( / *error* :getAveragePtOfSelectionPts adoc oVAR nVAR ss en pt wd el pte)
  
  (defun *error* (errmsg)
    (if (not (wcmatch errmsg "Function cancelled,quit / exit abort,console break,end"))
      (princ (strcat "\nError: " errmsg)))
    (vla-endundomark adoc)
    (mapcar 'setvar nVAR oVAR)
    (princ))
  
  (defun :getAveragePtOfSelectionPts (enx / id en sum pts)
    (setq id  (caar enx)
	  pts (cond ((= id 1)
		     (cdar (reverse (car enx))))
		    ((or (= id 2) (= id 3))
		     (mapcar 'cadr (cdadr enx)))
		    ((= id 4)
		     (mapcar 'cadr (cdddar enx)))
		    ((setq en (cadar enx))
		     (list (vlax-curve-getPointAtDist en (* 0.5 (vlax-curve-getDistAtPoint en (vlax-curve-getEndPoint en)))))))
	  sum '(0 0)
	  num (length pts))
    (foreach x pts (setq sum (mapcar '+ x sum)))
    (mapcar '/ sum (list num num)))
  
  ;--------
  
  (vla-startundomark (setq adoc (vla-get-activedocument (vlax-get-acad-object))))
  (setq oVAR (mapcar 'getvar (setq nVAR '(CMDECHO PEDITACCEPT CLAYER))))
  (mapcar 'setvar '(CMDECHO PEDITACCEPT) '(1 1))
  
  (if (and (setq ss (ssget "_:S" '((0 . "LWPOLYLINE,LINE,ARC"))))
	   (= 1 (sslength ss))
	   (setq en (ssname ss 0)
		 wd (cond ((= "LWPOLYLINE" (cdr (assoc 0 (entget en))))
			   (cdr (assoc 40 (entget en))))
			  (0.)))
	   (setq pt (:getAveragePtOfSelectionPts (ssnamex ss 0)))
	   (setq pt (vlax-curve-getClosestPointTo en pt))
	   (setq pt (if (> (vlax-curve-getDistAtPoint en pt)
			   (* 0.5 (vlax-curve-getDistAtPoint en (setq pte (vlax-curve-getEndPoint en)))))
		      (vlax-curve-getEndPoint en)
		      (vlax-curve-getStartPoint en)))
	   )
    (progn
      (setvar 'CMDECHO 0)
      (if (ssget "_P" '((0 . "LINE,ARC")))
	(progn
	  (command "_.PEDIT" en "")
	  (setq en (entlast))
	  (if (not (equal pte (vlax-curve-getEndPoint en) 1e-6))
	    (command "_.REVERSE" en ""))
	  ))
      (setvar 'CLAYER (cdr (assoc 8 (entget en))))
      (setq el (entlast))
      (setvar 'CMDECHO 1)
      (command "_.PLINE" (trans pt 0 1))
      (setvar 'CMDECHO 0)
      (command "_W" wd wd)
      (setvar 'CMDECHO 1)
      (while (> (getvar 'CMDACTIVE) 0)
	(command PAUSE))
      (setvar 'CMDECHO 0)
      (if (/= el (entlast))
	(command "_.JOIN" en (entlast) ""))))
  (*error* "end")
  )
